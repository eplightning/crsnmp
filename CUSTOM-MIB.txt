CUSTOM-MIB DEFINITIONS ::= BEGIN

IMPORTS
        private, NetworkAddress, IpAddress, Counter, Gauge,
                TimeTicks
            FROM RFC1155-SMI
        OBJECT-TYPE
                FROM RFC-1212;

mega-mib      OBJECT IDENTIFIER ::= { private 1234 }

-- private == 1.3.6.1.4

customInteger OBJECT-TYPE
    SYNTAX  INTEGER
    ACCESS  read-write
    STATUS  mandatory
    DESCRIPTION
            "Magiczny opis."
    ::= { mega-mib 6 }

time OBJECT-TYPE
    SYNTAX  Gauge
    ACCESS  read-write
    STATUS  mandatory
    DESCRIPTION
            "Magiczny opis."
    ::= { mega-mib 7 }

END
